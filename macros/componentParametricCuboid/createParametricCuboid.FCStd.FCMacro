#   CREATE PARAMETRIC CUBIOD
#   Copyright (C) 2024  Samuel Ellsworth
#   This program is free software: you can redistribute it and/or modify
#   it under the terms of the GNU General Public License as published by
#   the Free Software Foundation, either version 3 of the License, or
#   (at your option) any later version.

#   This program is distributed in the hope that it will be useful,
#   but WITHOUT ANY WARRANTY; without even the implied warranty of
#   MERCHANTABILITY or FITNESS FOR A PARTICULAR PURPOSE.  See the
#   GNU General Public License for more details.

#    You should have received a copy of the GNU General Public License
#    along with this program.  If not, see <https://www.gnu.org/licenses/>.

import FreeCAD as App
import FreeCADGui as Gui
import PartDesign
import Sketcher

# Create a new document
doc = App.newDocument("ParametricRectangle")

# Add a new spreadsheet
spreadsheet = doc.addObject("Spreadsheet::Sheet", "var")
spreadsheet.set("A2", "wid")
spreadsheet.set("A3", "thk")
spreadsheet.set("A4", "len")
spreadsheet.set("B2", "=\(25.4\)*1")  # Default width
spreadsheet.set("B3", "=\\(25.4\\)*1")   # Default thickness
spreadsheet.set("B4", "=\\\(25.4\\\)*1")   # Default padding length

# Set aliases for the cells
spreadsheet.setAlias("B2", "wid")
spreadsheet.setAlias("B3", "thk")
spreadsheet.setAlias("B4", "len")

# Recompute the document to apply changes in the spreadsheet
doc.recompute()

# Add a new body for the parametric sketch
body = doc.addObject("PartDesign::Body", "Body")

# Create a sketch on the XY plane
sketch = body.newObject("Sketcher::SketchObject", "RectangleSketch")
sketch.Support = (doc.getObject("XZ_Plane"), [''])
sketch.MapMode = "FlatFace"

# Gui.runCommand('Sketcher_CompCreateRectangles',0)
geoList = []
geoList.append(Part.LineSegment(App.Vector(-1.002072,0.919122,0),App.Vector(1.089203,0.919122,0)))
geoList.append(Part.LineSegment(App.Vector(1.089203,0.919122,0),App.Vector(1.089203,-0.525077,0)))
geoList.append(Part.LineSegment(App.Vector(1.089203,-0.525077,0),App.Vector(-1.002072,-0.525077,0)))
geoList.append(Part.LineSegment(App.Vector(-1.002072,-0.525077,0),App.Vector(-1.002072,0.919122,0)))
App.getDocument('ParametricRectangle').getObject('RectangleSketch').addGeometry(geoList,False)
conList = []
conList.append(Sketcher.Constraint('Coincident',0,2,1,1))
conList.append(Sketcher.Constraint('Coincident',1,2,2,1))
conList.append(Sketcher.Constraint('Coincident',2,2,3,1))
conList.append(Sketcher.Constraint('Coincident',3,2,0,1))
conList.append(Sketcher.Constraint('Horizontal',0))
conList.append(Sketcher.Constraint('Horizontal',2))
conList.append(Sketcher.Constraint('Vertical',1))
conList.append(Sketcher.Constraint('Vertical',3))
App.getDocument('ParametricRectangle').getObject('RectangleSketch').addConstraint(conList)
del geoList, conList

# Gui.runCommand('Sketcher_ConstrainSymmetric',0)
App.getDocument('ParametricRectangle').getObject('RectangleSketch').addConstraint(Sketcher.Constraint('Symmetric',0,2,2,2,-1,1))

# Gui.runCommand('Sketcher_ConstrainDistance',0)
App.getDocument('ParametricRectangle').getObject('RectangleSketch').addConstraint(Sketcher.Constraint('Distance',0,2,0,1,2.039680))
App.getDocument('ParametricRectangle').RectangleSketch.setExpression('Constraints[9]', u'var.wid')
App.getDocument('ParametricRectangle').getObject('RectangleSketch').addConstraint(Sketcher.Constraint('Distance',0,1,2,2,1.146353))
App.getDocument('ParametricRectangle').RectangleSketch.setExpression('Constraints[10]', u'var.thk')

# Gui.getDocument('ParametricRectangle').resetEdit()
App.ActiveDocument.recompute()

# Gui.Selection.addSelection('ParametricRectangle','Body','RectangleSketch.')
App.getDocument('ParametricRectangle').recompute()

### Begin command PartDesign_Pad
# Gui.getDocument('ParametricRectangle').ActiveView.setActiveObject('pdbody',App.getDocument('ParametricRectangle').getObject('Body'),'')
App.getDocument('ParametricRectangle').getObject('Body').newObject('PartDesign::Pad','Pad')
App.getDocument('ParametricRectangle').getObject('Pad').Profile = App.getDocument('ParametricRectangle').getObject('RectangleSketch')
App.getDocument('ParametricRectangle').getObject('Pad').Length = 10
App.ActiveDocument.recompute()
App.getDocument('ParametricRectangle').getObject('Pad').ReferenceAxis = (App.getDocument('ParametricRectangle').getObject('RectangleSketch'),['N_Axis'])
App.getDocument('ParametricRectangle').getObject('RectangleSketch').Visibility = False
App.ActiveDocument.recompute()
### End command PartDesign_Pad

App.getDocument('ParametricRectangle').Pad.setExpression('Length', u'var.len')
App.getDocument('ParametricRectangle').getObject('Pad').TaperAngle = 0.000000
App.getDocument('ParametricRectangle').getObject('Pad').UseCustomVector = 0
App.getDocument('ParametricRectangle').getObject('Pad').Direction = (0, -1, 0)
App.getDocument('ParametricRectangle').getObject('Pad').ReferenceAxis = (App.getDocument('ParametricRectangle').getObject('RectangleSketch'), ['N_Axis'])
App.getDocument('ParametricRectangle').getObject('Pad').AlongSketchNormal = 1
App.getDocument('ParametricRectangle').getObject('Pad').Type = 0
App.getDocument('ParametricRectangle').getObject('Pad').UpToFace = None
App.getDocument('ParametricRectangle').getObject('Pad').Reversed = 0
App.getDocument('ParametricRectangle').getObject('Pad').Midplane = 0
App.getDocument('ParametricRectangle').getObject('Pad').Offset = 0
App.getDocument('ParametricRectangle').recompute()
App.getDocument('ParametricRectangle').getObject('RectangleSketch').Visibility = False
 
App.ActiveDocument.recompute()
App.getDocument('ParametricRectangle').recompute()

# Gui.SendMsgToActiveView("Save")
App.getDocument("ParametricRectangle").saveAs(u"C:/Users/18055/Documents/freeCAD/20241110wormBinParametric/rectangularPrism.FCStd")
### End command Std_Save

Gui.activeDocument().activeView().viewIsometric()
Gui.SendMsgToActiveView("ViewFit")
doc.recompute()
